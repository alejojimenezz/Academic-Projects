(setq ent (car (entsel "\nSeleccione bloque: ")))
(setq datos (entget ent))

(setq ename      (cdr (assoc -1 datos)))
(setq tipo       (cdr (assoc 0 datos)))
(setq owner      (cdr (assoc 330 datos)))
(setq handle     (cdr (assoc 5 datos)))
(setq layer      (cdr (assoc 8 datos)))
(setq nombreBlk  (cdr (assoc 2 datos)))
(setq insercion  (cdr (assoc 10 datos)))
(setq escalaX    (cdr (assoc 41 datos)))
(setq escalaY    (cdr (assoc 42 datos)))
(setq escalaZ    (cdr (assoc 43 datos)))
(setq rotacion   (cdr (assoc 50 datos)))
